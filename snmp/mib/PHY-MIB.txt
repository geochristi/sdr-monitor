PHY-MIB DEFINITIONS ::= BEGIN

IMPORTS
    MODULE-IDENTITY,
    OBJECT-TYPE,
    Integer32,
    enterprises
        FROM SNMPv2-SMI
    DisplayString
        FROM SNMPv2-TC;

phy MODULE-IDENTITY
    LAST-UPDATED "202603170000Z"
    ORGANIZATION "SDR PHY Thesis"
    CONTACT-INFO "Georgia Christi"
    DESCRIPTION
        "MIB module for monitoring and controlling the GNU Radio PHY."
    ::= { enterprises 53864 }

phyObjects OBJECT IDENTIFIER ::= { phy 1 }

-- Scalar instance OIDs used by the handler:
-- phyNoise    = .1.3.6.1.4.1.53864.1.1.0
-- phyBits     = .1.3.6.1.4.1.53864.1.2.0
-- phyErrors   = .1.3.6.1.4.1.53864.1.3.0
-- phyBER      = .1.3.6.1.4.1.53864.1.4.0
-- phyResetBER = .1.3.6.1.4.1.53864.1.5.0
-- phyPacketRate = .1.3.6.1.4.1.53864.1.6.0
-- phyFreqOffset = .1.3.6.1.4.1.53864.1.7.0
-- phyModScheme = .1.3.6.1.4.1.53864.1.8.0
-- phySNR      = .1.3.6.1.4.1.53864.1.9.0
-- phyBERInject = .1.3.6.1.4.1.53864.1.10.0

phyNoise OBJECT-TYPE
    SYNTAX      Integer32
    MAX-ACCESS  read-write
    STATUS      current
    DESCRIPTION
        "Explicit additive noise voltage, scaled by 10.
         Example: value 5 means noise=0.5.
         (scalar instance .1.3.6.1.4.1.53864.1.1.0)."
    ::= { phyObjects 1 }

phyBits OBJECT-TYPE
    SYNTAX      Integer32
    MAX-ACCESS  read-only
    STATUS      current
    DESCRIPTION
        "Total bits processed by the PHY (scalar instance .1.3.6.1.4.1.53864.1.2.0)."
    ::= { phyObjects 2 }

phyErrors OBJECT-TYPE
    SYNTAX      Integer32
    MAX-ACCESS  read-only
    STATUS      current
    DESCRIPTION
        "Bit errors detected by the PHY (scalar instance .1.3.6.1.4.1.53864.1.3.0)."
    ::= { phyObjects 3 }

phyBER OBJECT-TYPE
    SYNTAX      DisplayString
    MAX-ACCESS  read-only
    STATUS      current
    DESCRIPTION
        "Bit Error Rate (scalar instance .1.3.6.1.4.1.53864.1.4.0)."
    ::= { phyObjects 4 }

phyResetBER OBJECT-TYPE
    SYNTAX      Integer32
    MAX-ACCESS  read-write
    STATUS      current
    DESCRIPTION
        "Write 1 to reset the BER counters (bits, errors, BER).
         Always returns 0 on read.
         (scalar instance .1.3.6.1.4.1.53864.1.5.0)."
    ::= { phyObjects 5 }

phyPacketRate OBJECT-TYPE
    SYNTAX      Integer32
    MAX-ACCESS  read-write
    STATUS      current
    DESCRIPTION
        "Packet generation rate (packets/sec).
         (scalar instance .1.3.6.1.4.1.53864.1.6.0)."
    ::= { phyObjects 6 }

phyFreqOffset OBJECT-TYPE
    SYNTAX      Integer32
    MAX-ACCESS  read-write
    STATUS      current
    DESCRIPTION
        "Frequency offset in Hz.
         (scalar instance .1.3.6.1.4.1.53864.1.7.0)."
    ::= { phyObjects 7 }

phyModScheme OBJECT-TYPE
    SYNTAX      Integer32
    MAX-ACCESS  read-write
    STATUS      current
    DESCRIPTION
        "Modulation scheme selector:
         0=BPSK, 1=QPSK, 2=8PSK, 3=16QAM, 4=64QAM.
         (scalar instance .1.3.6.1.4.1.53864.1.8.0)."
    ::= { phyObjects 8 }

phySNR OBJECT-TYPE
    SYNTAX      Integer32
    MAX-ACCESS  read-write
    STATUS      current
    DESCRIPTION
        "Target channel SNR in dB, scaled by 10.
         Example: value 250 means 25.0 dB.
         (scalar instance .1.3.6.1.4.1.53864.1.9.0)."
    ::= { phyObjects 9 }

phyBERInject OBJECT-TYPE
    SYNTAX      Integer32
    MAX-ACCESS  read-write
    STATUS      current
    DESCRIPTION
        "BER injection probability scaled by 1,000,000.
         Example: value 10000 means 0.01 (1%).
         (scalar instance .1.3.6.1.4.1.53864.1.10.0)."
    ::= { phyObjects 10 }

END
