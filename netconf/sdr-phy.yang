module sdr-phy {
  namespace "urn:sdr:phy";
  prefix sdr;

  container phy {

    leaf frequency_offset {
      type int32 {
        range "-1000000..1000000";
      }
      default 0;
      description "Frequency offset in Hz";
    }

    leaf tx_gain {
      type decimal64 {
        fraction-digits 2;
      }
      default 10;
    }

    leaf rx_gain {
      type decimal64 {
        fraction-digits 2;
      }
      default 10;
    }

    leaf mod_scheme {
      type uint32 {
        range "0..4";
      }
      default 3;
    }

    leaf packet_rate {
      type uint32;
      default 100;
    }

    leaf noise_level {
      type decimal64 {
        fraction-digits 4;
      }
      default 0;
    }

    leaf snr {
      type decimal64 {
        fraction-digits 2;
      }
      default 30;
      description "Target SNR in dB";
    }

    leaf ber_inject {
      type decimal64 {
        fraction-digits 6;
      }
      default 0;
      description "BER injection probability in [0,1]";
    }
  }
}
